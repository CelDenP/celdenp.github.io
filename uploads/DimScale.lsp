;;; Основная функция для изменения масштаба линейных размеров
(defun update_dimlfac (val)
  ;; Изменяем системную переменную масштаба линейных размеров
  (setvar "DIMLFAC" val)
  ;; Выводим сообщение об успешном изменении в командную строку
  (princ (strcat "\nМасштаб линейных размеров установлен на: " (vl-princ-to-string val)))
  (princ)
)

;;; =======================================================
;;; Команды с АНГЛИЙСКОЙ буквой "M"
;;; =======================================================
(defun c:M100_VD () (update_dimlfac 1.0))
(defun c:M50_VD ()  (update_dimlfac 0.5))
(defun c:M20_VD ()  (update_dimlfac 0.2))
(defun c:M10_VD ()  (update_dimlfac 0.1))
(defun c:M5_VD ()   (update_dimlfac 0.05))
(defun c:M1_VD ()   (update_dimlfac 0.001))

;;; =======================================================
;;; Команды с РУССКОЙ буквой "М"
;;; =======================================================
(defun c:М100_VD () (c:M100_VD))
(defun c:М50_VD ()  (c:M50_VD))
(defun c:М20_VD ()  (c:M20_VD))
(defun c:М10_VD ()  (c:M10_VD))
(defun c:М5_VD ()   (c:M5_VD))
(defun c:М1_VD ()   (c:M1_VD))
